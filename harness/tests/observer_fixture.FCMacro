# Deterministic observer test only. Not used by agent benchmarks or production sessions.
def _fixture():
    import FreeCAD as App
    import FreeCADGui as Gui
    import Part
    import Sketcher
    doc = App.newDocument("ObserverFixture")
    body = doc.addObject("PartDesign::Body", "Body")
    sketch = body.newObject("Sketcher::SketchObject", "Sketch")
    sketch.addGeometry(Part.LineSegment(App.Vector(0, 0, 0), App.Vector(12, 0, 0)), False)
    sketch.addConstraint(Sketcher.Constraint("Distance", 0, 12.0))
    doc.recompute()
    Gui.activeDocument().setEdit(sketch.Name)
    Gui.Selection.addSelection(doc.Name, sketch.Name, "Edge1")

# Do not enter edit mode while FreeCAD is still applying its startup stylesheet.
from PySide6 import QtCore
QtCore.QTimer.singleShot(4000, _fixture)
